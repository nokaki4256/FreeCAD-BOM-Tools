import FreeCAD as App
import Spreadsheet

# ==========================================
# 1. ドキュメントとスプレッドシートの取得
# ==========================================
doc = App.ActiveDocument

# ※もしスプレッドシートの名前が異なる場合は、ここの名前を変更してください
sheet_bom = doc.getObject("BOM")
sheet_assy = doc.getObject("BOM_Assy")

if not sheet_bom or not sheet_assy:
    App.Console.PrintError("エラー: 'BOM' または 'BOM_Assy' スプレッドシートが見つかりません。\n")
else:
    # ==========================================
    # 2. BOM_Assy データの辞書化（展開用のルールブック作成）
    # ==========================================
    assy_dict = {}
    row = 2
    while True:
        try:
            # セルが存在しない領域（表の末尾以降）を読もうとするとValueErrorが出るため検知
            parent = sheet_assy.get("A" + str(row))
            child = sheet_assy.get("B" + str(row))
            qty_str = sheet_assy.get("C" + str(row))
        except ValueError:
            # エラーが出たらスプレッドシートの限界なのでループ終了
            break
            
        # A列とB列が両方とも空なら読み取り終了
        if not parent and not child:
            break
            
        if parent and child and qty_str:
            try:
                qty = int(qty_str)
            except ValueError:
                qty = 1
                
            if parent not in assy_dict:
                assy_dict[parent] = []
            assy_dict[parent].append((child, qty))
        
        row += 1

    # ==========================================
    # 3. BOM データのリスト化（展開元のベースデータ）
    # ==========================================
    bom_list = []
    row = 2
    while True:
        try:
            part = sheet_bom.get("A" + str(row))
            qty_str = sheet_bom.get("B" + str(row))
        except ValueError:
            break
            
        if not part:
            break
            
        if part and qty_str:
            try:
                qty = int(qty_str)
            except ValueError:
                qty = 1
            bom_list.append((part, qty))
            
        row += 1
        
        ###
# ==========================================
    # 4. 統合版リストの計算処理
    # ==========================================
    import re

    # 最終的な部品データを格納する辞書
    # 構造: final_bom["ベース部品名"] = {"qty": 総数量, "maker": "メーカー名"}
    final_bom = {}

    def add_to_final(raw_name, add_qty):
        # カッコ内のメーカー名と、カッコを除外したベース部品名に分割
        match = re.search(r'[(（](.*?)[)）]', raw_name)
        if match:
            maker = match.group(1).strip()
            base_name = re.sub(r'[(（].*?[)）]', '', raw_name).strip()
        else:
            maker = ""
            base_name = raw_name.strip()

        # 初めて登場するベース部品名なら辞書に登録
        if base_name not in final_bom:
            final_bom[base_name] = {"qty": 0, "maker": ""}
        
        # 数量を合算
        final_bom[base_name]["qty"] += add_qty
        
        # メーカー名がまだ空欄で、今回の名前にメーカー名が含まれていれば上書き記録
        if final_bom[base_name]["maker"] == "" and maker != "":
            final_bom[base_name]["maker"] = maker

    for part, qty in bom_list:
        # アセンブリ展開用のベース名（親アセンブリ名にカッコが付いていた場合の保険）
        part_base = re.sub(r'[(（].*?[)）]', '', part).strip()
        
        # パターンB: アセンブリ（BOM_AssyのA列に名前が存在する）場合
        if part in assy_dict:
            for child_name, child_qty in assy_dict[part]:
                add_to_final(child_name, qty * child_qty)
        elif part_base in assy_dict:
            for child_name, child_qty in assy_dict[part_base]:
                add_to_final(child_name, qty * child_qty)
                
        # パターンA: 単独の部品（BOM_Assyに存在しない）場合
        else:
            add_to_final(part, qty)

    # 既存BOM削除
    try:
        doc.removeObject("BOM_Total")
    except:
        pass

# ==========================================
    # 5. 新しいスプレッドシートとCSVへの出力
    # ==========================================
    import time
    import os
    import csv

    timestamp = time.strftime("%H%M%S")
    sheet_name = "BOM_Total"
    new_sheet = doc.addObject("Spreadsheet::Sheet", sheet_name)

    # ヘッダーの書き込み
    new_sheet.set("A1", "部品名称")
    new_sheet.set("B1", "メーカー名")
    new_sheet.set("C1", "総数量")
    new_sheet.setStyle("A1:C1", "bold", "add")

    # データをソート（メーカー名昇順 → 部品名昇順）
    sorted_bom = sorted(final_bom.items(), key=lambda item: (item[1]["maker"], item[0]))

    # CSV出力用のファイルパスを設定（FreeCADファイルと同じ場所に保存）
    # ※ファイルが未保存の場合は、マクロの実行フォルダに保存されます
    doc_filename = doc.FileName
    if doc_filename:
        export_dir = os.path.dirname(doc_filename)
    else:
        export_dir = App.getUserMacroDir(True)
    
    csv_path = os.path.join(export_dir, f"BOM_Total_{timestamp}.csv")

    # データの書き込み
    row = 2
    csv_data = [["部品名称", "メーカー名", "総数量"]] # CSV用のヘッダー行

    for base_name, data in sorted_bom:
        # スプレッドシートへの書き込み
        new_sheet.set("A" + str(row), base_name)
        new_sheet.set("B" + str(row), data["maker"])
        new_sheet.set("C" + str(row), str(data["qty"]))
        row += 1
        
        # CSV用のデータとして追加
        csv_data.append([base_name, data["maker"], data["qty"]])

    # CSVファイルの書き出し
    # Excelで文字化けしないよう、BOM付きUTF-8 (utf-8-sig) で保存します
    try:
        with open(csv_path, mode="w", newline="", encoding="utf-8-sig") as f:
            writer = csv.writer(f)
            writer.writerows(csv_data)
        csv_msg = f"\nCSVファイルも保存しました:\n{csv_path}"
    except Exception as e:
        csv_msg = f"\n※CSV保存エラー: {e}"

    # スプレッドシートの再計算と画面更新
    doc.recompute()
    App.Console.PrintMessage(f"統合版リスト「{sheet_name}」の作成が完了しました。{csv_msg}\n")
