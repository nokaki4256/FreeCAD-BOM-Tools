import FreeCAD as App
import Spreadsheet

# ==========================================
# 1. ドキュメントとスプレッドシートの取得
# ==========================================
doc = App.ActiveDocument

# ※もしスプレッドシートの名前が異なる場合は、ここの名前を変更してください
sheet_bom = doc.getObject("BOM")
sheet_assy = doc.getObject("BOM_Assy")

if not sheet_bom or not sheet_assy:
    App.Console.PrintError("エラー: 'BOM' または 'BOM_Assy' スプレッドシートが見つかりません。\n")
else:
    # ==========================================
    # 2. BOM_Assy データの辞書化（展開用のルールブック作成）
    # ==========================================
    assy_dict = {}
    row = 2
    while True:
        try:
            # セルが存在しない領域（表の末尾以降）を読もうとするとValueErrorが出るため検知
            parent = sheet_assy.get("A" + str(row))
            child = sheet_assy.get("B" + str(row))
            qty_str = sheet_assy.get("C" + str(row))
        except ValueError:
            # エラーが出たらスプレッドシートの限界なのでループ終了
            break
            
        # A列とB列が両方とも空なら読み取り終了
        if not parent and not child:
            break
            
        if parent and child and qty_str:
            try:
                qty = int(qty_str)
            except ValueError:
                qty = 1
                
            if parent not in assy_dict:
                assy_dict[parent] = []
            assy_dict[parent].append((child, qty))
        
        row += 1

    # ==========================================
    # 3. BOM データのリスト化（展開元のベースデータ）
    # ==========================================
    bom_list = []
    row = 2
    while True:
        try:
            part = sheet_bom.get("A" + str(row))
            qty_str = sheet_bom.get("B" + str(row))
        except ValueError:
            break
            
        if not part:
            break
            
        if part and qty_str:
            try:
                qty = int(qty_str)
            except ValueError:
                qty = 1
            bom_list.append((part, qty))
            
        row += 1
        
        ###
# ==========================================
    # 4. 統合版リストの計算処理
    # ==========================================
    # 最終的な部品と総数量を格納する辞書（同じ部品が複数回出てきたら合算します）
    final_bom = {}

    for part, qty in bom_list:
        # パターンB: アセンブリ（BOM_AssyのA列に名前が存在する）場合
        if part in assy_dict:
            # BOM_Assyに登録されている構成部品をすべて展開して掛け算
            for child_name, child_qty in assy_dict[part]:
                total_qty = qty * child_qty
                
                # 統合版リストに追加（既に同じ部品があれば足し算）
                if child_name in final_bom:
                    final_bom[child_name] += total_qty
                else:
                    final_bom[child_name] = total_qty
                    
        # パターンA: 単独の部品（BOM_Assyに存在しない）場合
        else:
            # そのままの数量で統合版リストに追加
            if part in final_bom:
                final_bom[part] += qty
            else:
                final_bom[part] = qty

    # ==========================================
    # 5. 新しいスプレッドシートへの出力
    # ==========================================
    # 新しいスプレッドシートの作成
    # 実行するたびに上書きされないよう、ユニークな名前を付けます
    import time
    timestamp = time.strftime("%H%M%S")
    sheet_name = "BOM_Total_" + timestamp
    new_sheet = doc.addObject("Spreadsheet::Sheet", sheet_name)

    # ヘッダーの書き込み
    new_sheet.set("A1", "部品名称")
    new_sheet.set("B1", "総数量")
    new_sheet.setStyle("A1:B1", "bold", "add")

    # データの書き込み（2行目からスタート）
    row = 2
    for name, total in final_bom.items():
        new_sheet.set("A" + str(row), name)
        new_sheet.set("B" + str(row), str(total))
        row += 1

    # スプレッドシートの再計算と画面更新
    doc.recompute()
    App.Console.PrintMessage(f"統合版リスト「{sheet_name}」の作成が完了しました。\n")
